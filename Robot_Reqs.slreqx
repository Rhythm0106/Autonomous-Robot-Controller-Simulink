# Robot_Reqs

## R1: Forward Motion (Functional)
Robot must move forward if no obstacles are detected.
- Rationale: Robot must move forward if no obstacles are detected

## R2: Obstacle Detection (Functional)
Robot must stop if front sensor < threshold.
- Rationale: Robot must stop if front sensor < threshold.

## R3: Left Avoidance (Functional)
Robot turns left if front & right blocked, left free
- Rationale: Robot turns left if front & right blocked, left free.

## R4: Right Avoidance (Functional)
Robot turns right if front & left blocked, right free.
- Rationale: Robot turns right if front & left blocked, right free.

## R5: Stop All (Functional)
If all directions blocked, robot must stop.
- Rationale: If all directions blocked, robot must stop

## R6: Resume (Functional)
Robot resumes movement when any path is free.
- Rationale: Robot resumes movement when any path is free.

## R7: Motor Output (Functional)
Each state must output valid PWM to motor block
- Rationale: Each state must output valid PWM to motor block

## R8: Velocity Cap (Functional)
Robot speed must not exceed 0.5 m/s.
- Rationale: Robot speed must not exceed 0.5 m/s.

## R9: Kinematic Accuracy (Functional)
Differential drive model must be used for motion.
- Rationale: Differential drive model must be used for motion.

## R10: MIL vs SIL (Functional)
SIL and MIL results must match within 5%.
- Rationale: SIL and MIL results must match within 5%.

## R11: Code Constraints (Functional)
Code must compile using Embedded Coder settings.
- Rationale: Code must compile using Embedded Coder settings.

## R12: Coverage (Functional)
- Rationale: Model must reach 90% decision + condition coverage.

## R13: Logging (Functional)
- Rationale: Log sensor and velocity data to mat file.

## R14: Emergency Stop (Functional)
- Rationale: Emergency flag must override and stop robot

## R15: Battery Fault (Functional)
- Rationale: Stop if simulated battery voltage drops below 10V.
